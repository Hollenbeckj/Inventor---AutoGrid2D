' CreateGrid2D - clipped grid, bold dash-dot center axes and center circle.
' Spacing is a model distance; directions are drawing-sheet X/Y.
' Center is the area centroid, not the bounding-box center.
' Geometry is a snapshot. Rerun after changing the model boundary.
Imports System.Collections.Generic

Sub Main()
    Const TITLE As String = "Create Grid"
    Const TOL As Double = 0.000001 ' Sheet centimeters (0.00001 mm).
    Const MAX_LINES As Integer = 2000
    Const GRID_WEIGHT As Double = 0.018 ' 0.18 mm on paper.
    Const CENTER_WEIGHT As Double = 0.1 ' 1.00 mm on paper.
    Const CENTER_PATTERN_SCALE As Double = 4.0 ' Longer dashes/gaps, fewer repeats.

    If ThisApplication.ActiveDocumentType <> DocumentTypeEnum.kDrawingDocumentObject Then
        MessageBox.Show("Open an Inventor drawing first.", TITLE)
        Exit Sub
    End If

    Dim doc As DrawingDocument = ThisApplication.ActiveDocument
    Dim sketch As DrawingSketch = Nothing
    Dim transaction As Transaction = Nothing
    Dim editing As Boolean = False
    Try
        Dim edges As New List(Of Double())
        Dim view As DrawingView = Nothing
        For i As Integer = 0 To 3
            Dim segment As DrawingCurveSegment = Nothing
            Try
                segment = TryCast(ThisApplication.CommandManager.Pick( _
                    SelectionFilterEnum.kDrawingCurveSegmentFilter, _
                    "Select one straight segment on outer side " & (i + 1) & " of 4 (Esc cancels)"), DrawingCurveSegment)
            Catch cancelled As System.Runtime.InteropServices.COMException When cancelled.ErrorCode = -2147467260
                Exit Sub ' E_ABORT: interactive selection was cancelled.
            End Try
            If segment Is Nothing Then Exit Sub
            If segment.GeometryType <> Curve2dTypeEnum.kLineSegmentCurve2d Then
                Throw New InvalidOperationException("Select four straight boundary edges.")
            End If
            Dim pickedView As DrawingView = segment.Parent.Parent
            If view Is Nothing Then
                view = pickedView
            ElseIf Not (pickedView Is view) Then
                Throw New InvalidOperationException("All four edges must belong to the same drawing view.")
            End If
            Dim a As Point2d = segment.StartPoint
            Dim b As Point2d = segment.EndPoint
            edges.Add(New Double() {a.X, a.Y, b.X, b.Y})
        Next

        For Each existing As DrawingSketch In view.Sketches
            If String.Equals(existing.Name, "Grid", StringComparison.OrdinalIgnoreCase) Then
                Throw New InvalidOperationException("This view already contains a 'Grid' sketch. " & _
                    "Delete or rename it before regenerating the grid.")
            End If
        Next

        Dim polygon As List(Of Double()) = BoundaryFromSides(edges, TOL)
        Dim center As Double() = AreaCentroid(polygon, TOL)
        Dim minX As Double = Double.MaxValue, minY As Double = Double.MaxValue
        Dim maxX As Double = Double.MinValue, maxY As Double = Double.MinValue
        For Each p As Double() In polygon
            minX = Math.Min(minX, p(0)) : maxX = Math.Max(maxX, p(0))
            minY = Math.Min(minY, p(1)) : maxY = Math.Max(maxY, p(1))
        Next

        Dim uom As UnitsOfMeasure = doc.UnitsOfMeasure
        Dim unitName As String = uom.GetStringFromType(uom.LengthUnits)
        Dim spacingX As Double = ReadSpacing(uom, "X spacing (between vertical grid lines)", unitName)
        If spacingX = 0 Then Exit Sub
        Dim spacingY As Double = ReadSpacing(uom, "Y spacing (between horizontal grid lines)", unitName)
        If spacingY = 0 Then Exit Sub
        If Not IsFinitePositive(view.Scale) Then Throw New InvalidOperationException("Invalid drawing-view scale.")
        spacingX *= view.Scale
        spacingY *= view.Scale
        ' Sheet-space radius: half the smaller selected model spacing, scaled once.
        Dim centerRadius As Double = Math.Min(spacingX, spacingY) / 2.0
        Dim countX As Integer = InteriorCount(maxX - minX, spacingX, TOL, MAX_LINES)
        Dim countY As Integer = InteriorCount(maxY - minY, spacingY, TOL, MAX_LINES)
        If countX + countY > MAX_LINES Then
            Throw New InvalidOperationException("Too many grid lines. Increase the spacing (maximum " & MAX_LINES & " grid positions).")
        End If

        ' Plan every clipped segment before making any document changes.
        Dim gridLines As New List(Of Double())
        For i As Integer = 1 To countX
            Dim x As Double = minX + i * spacingX
            ' A center axis replaces a coincident grid line; avoid overlapping entities.
            If Math.Abs(x - center(0)) > TOL Then gridLines.AddRange(ClipAxis(polygon, True, x, TOL))
        Next
        For i As Integer = 1 To countY
            Dim y As Double = minY + i * spacingY
            If Math.Abs(y - center(1)) > TOL Then gridLines.AddRange(ClipAxis(polygon, False, y, TOL))
        Next
        Dim centerLines As New List(Of Double())
        centerLines.AddRange(ClipAxis(polygon, True, center(0), TOL))
        centerLines.AddRange(ClipAxis(polygon, False, center(1), TOL))
        If centerLines.Count = 0 Then Throw New InvalidOperationException("Could not construct the center mark.")
        If Not InsidePolygon(polygon, center, TOL) Then
            MessageBox.Show("This concave shape's area centroid lies outside its boundary. " & _
                "The bold center axes will be clipped to the shape and will not cross inside it.", TITLE)
        End If
        If gridLines.Count + centerLines.Count + 1 > MAX_LINES Then
            Throw New InvalidOperationException("Too many grid entities including the center circle. Increase the grid spacing.")
        End If
        If countX + countY = 0 Then
            MessageBox.Show("The spacing exceeds the shape dimensions. Only the bold center mark will be created.", TITLE)
        End If

        transaction = ThisApplication.TransactionManager.StartTransaction(doc, TITLE)
        Dim gridLayer As Layer = GetGridLayer(doc, "2D-Grid", GRID_WEIGHT, False)
        Dim centerLayer As Layer = GetGridLayer(doc, "2D-Grid-Center", CENTER_WEIGHT, True)
        sketch = view.Sketches.Add()
        sketch.Name = "Grid"
        sketch.Edit()
        editing = True
        sketch.DeferUpdates = True
        For Each line As Double() In gridLines
            AddGridLine(sketch, gridLayer, line, GRID_WEIGHT, False)
        Next
        For Each line As Double() In centerLines
            AddGridLine(sketch, centerLayer, line, CENTER_WEIGHT, True, CENTER_PATTERN_SCALE)
        Next
        AddCenterCircle(sketch, centerLayer, center, centerRadius, CENTER_WEIGHT, CENTER_PATTERN_SCALE)
        sketch.DeferUpdates = False
        sketch.ExitEdit()
        editing = False
        If Not doc.Update2(False) Then Throw New InvalidOperationException("Inventor could not update the drawing.")
        transaction.End()
        transaction = Nothing
        MessageBox.Show("Grid created successfully." & vbCrLf & _
            "Grid segments: " & gridLines.Count & vbCrLf & _
            "Bold center segments: " & centerLines.Count & vbCrLf & _
            "Center circle: radius = half the smaller grid spacing." & vbCrLf & _
            "Center: area centroid; axes span the selected boundary.", TITLE)
    Catch ex As Exception
        Dim cleanupErrors As String = ""
        If editing AndAlso sketch IsNot Nothing Then
            Try
                sketch.ExitEdit()
            Catch cleanup As Exception
                cleanupErrors &= vbCrLf & "Exit sketch: " & cleanup.Message
            End Try
        End If
        If transaction IsNot Nothing Then
            Try
                transaction.Abort()
            Catch cleanup As Exception
                cleanupErrors &= vbCrLf & "Rollback: " & cleanup.Message
            End Try
        End If
        MessageBox.Show("The grid could not be created." & vbCrLf & ex.Message & cleanupErrors, _
            TITLE, MessageBoxButtons.OK, MessageBoxIcon.Error)
    End Try
End Sub

Function ReadSpacing(uom As UnitsOfMeasure, label As String, unitName As String) As Double
    Dim previous As String = "12 " & unitName
    Do
        Dim entry As String = InputBox("Enter model distance for " & label & "." & vbCrLf & _
            "Bare numbers use drawing units: " & unitName & "." & vbCrLf & _
            "Examples: 12 in, 300 mm. Cancel leaves the drawing unchanged.", label, previous)
        If entry = "" Then Return 0
        previous = entry
        Try
            Dim value As Double = uom.GetValueFromExpression(entry.Trim(), UnitsTypeEnum.kDefaultDisplayLengthUnits)
            If IsFinitePositive(value) Then Return value
        Catch ex As Exception
            ' Invalid expressions are retried without losing the selections.
        End Try
        MessageBox.Show("Enter a valid length greater than zero.", "Grid spacing")
    Loop
End Function

Function GetGridLayer(doc As DrawingDocument, name As String, weight As Double, bold As Boolean) As Layer
    ' Enumerate instead of interpreting any COM exception as a missing layer.
    For Each existing As Layer In doc.StylesManager.Layers
        If String.Equals(existing.Name, name, StringComparison.OrdinalIgnoreCase) Then
            If Not existing.Visible OrElse Not existing.Plot Then
                Throw New InvalidOperationException("Layer '" & name & "' must be visible and enabled for printing.")
            End If
            Return existing ' Preserve formatting shared with other entities.
        End If
    Next
    Dim baseLayer As Layer = doc.StylesManager.ActiveStandardStyle.ActiveObjectDefaults.SketchGeometryLayer
    Dim result As Layer = baseLayer.Copy(name)
    result.Color = ThisApplication.TransientObjects.CreateColor(If(bold, 0, 128), If(bold, 0, 128), If(bold, 0, 128))
    result.LineWeight = weight
    result.LineType = If(bold, LineTypeEnum.kLongDashDottedLineType, LineTypeEnum.kContinuousLineType)
    result.Visible = True
    result.Plot = True
    Return result
End Function

Sub AddGridLine(sketch As DrawingSketch, layer As Layer, coordinates As Double(), weight As Double, bold As Boolean, _
                Optional patternScale As Double = 1.0)
    Dim tg As TransientGeometry = ThisApplication.TransientGeometry
    Dim a As Point2d = sketch.SheetToSketchSpace(tg.CreatePoint2d(coordinates(0), coordinates(1)))
    Dim b As Point2d = sketch.SheetToSketchSpace(tg.CreatePoint2d(coordinates(2), coordinates(3)))
    Dim line As SketchLine = sketch.SketchLines.AddByTwoPoints(a, b)
    line.Layer = layer
    line.LineDefinitionSpace = LineDefinitionSpaceEnum.kModelSpace
    ' Override each entity too: an existing center layer may still be continuous.
    line.LineType = If(bold, LineTypeEnum.kLongDashDottedLineType, LineTypeEnum.kContinuousLineType)
    line.LineScale = patternScale
    line.LineWeight = weight
    line.OverrideColor = ThisApplication.TransientObjects.CreateColor(If(bold, 0, 128), If(bold, 0, 128), If(bold, 0, 128))
End Sub

' Convert both center and a radius endpoint through the sketch transform.
' Using the sheet radius directly in AddByCenterRadius would be wrong for a
' view sketch whose coordinate scale differs from sheet space.
Sub AddCenterCircle(sketch As DrawingSketch, layer As Layer, center As Double(), sheetRadius As Double, _
                    weight As Double, patternScale As Double)
    Dim tg As TransientGeometry = ThisApplication.TransientGeometry
    Dim sketchCenter As Point2d = sketch.SheetToSketchSpace(tg.CreatePoint2d(center(0), center(1)))
    Dim sketchRim As Point2d = sketch.SheetToSketchSpace(tg.CreatePoint2d(center(0) + sheetRadius, center(1)))
    Dim radius As Double = sketchCenter.DistanceTo(sketchRim)
    If Not IsFinitePositive(radius) Then Throw New InvalidOperationException("The center circle radius is invalid.")
    Dim circle As SketchCircle = sketch.SketchCircles.AddByCenterRadius(sketchCenter, radius)
    circle.Layer = layer
    circle.LineDefinitionSpace = LineDefinitionSpaceEnum.kModelSpace
    circle.LineType = LineTypeEnum.kLongDashDottedLineType
    circle.LineScale = patternScale
    circle.LineWeight = weight
    circle.OverrideColor = ThisApplication.TransientObjects.CreateColor(0, 0, 0)
End Sub

' GEOMETRY KERNEL BEGIN - no Inventor dependencies, also used by regression tests.
Function IsFinitePositive(value As Double) As Boolean
    Return Not Double.IsNaN(value) AndAlso Not Double.IsInfinity(value) AndAlso value > 0
End Function

Function Near(a As Double(), b As Double(), tol As Double) As Boolean
    Return Math.Abs(a(0) - b(0)) <= tol AndAlso Math.Abs(a(1) - b(1)) <= tol
End Function

Function Cross(a As Double(), b As Double(), c As Double()) As Double
    Return (b(0) - a(0)) * (c(1) - a(1)) - (b(1) - a(1)) * (c(0) - a(0))
End Function

Function BoundaryFromSides(edges As List(Of Double()), tol As Double) As List(Of Double())
    ' Preserve exact closed boundaries, including concave quadrilaterals.
    Try
        Return OrderBoundary(edges, tol)
    Catch disconnected As InvalidOperationException
        ' Drawing edges may end at an occlusion or a split instead of a corner.
        ' Recover a unique convex outline from the four supporting straight lines.
    End Try
    If edges.Count <> 4 Then Throw New InvalidOperationException("Select exactly four sides.")
    For i As Integer = 0 To 3
        Dim edge As Double() = edges(i)
        Dim dx As Double = edge(2) - edge(0), dy As Double = edge(3) - edge(1)
        Dim length As Double = Math.Sqrt(dx * dx + dy * dy)
        If Not IsFinitePositive(length) OrElse length <= tol Then
            Throw New InvalidOperationException("A selected segment has zero or negligible length.")
        End If
        For j As Integer = 0 To i - 1
            Dim prior As Double() = edges(j)
            Dim px As Double = prior(2) - prior(0), py As Double = prior(3) - prior(1)
            Dim priorLength As Double = Math.Sqrt(px * px + py * py)
            Dim sine As Double = (dx / length) * (py / priorLength) - (dy / length) * (px / priorLength)
            Dim distance As Double = Math.Abs((prior(0) - edge(0)) * dy / length - (prior(1) - edge(1)) * dx / length)
            If Math.Abs(sine) <= 0.00000001 AndAlso distance <= tol Then
                Throw New InvalidOperationException("Two picks are on the same straight side. Select one segment on each of four different outer sides.")
            End If
        Next
    Next

    Dim found As List(Of Double()) = Nothing
    ' Fix the first side and try the six possible orders of the other three.
    For second As Integer = 1 To 3
        For third As Integer = 1 To 3
            If third = second Then Continue For
            Dim fourth As Integer = 6 - second - third
            Dim order As Integer() = {0, second, third, fourth}
            Dim polygon As New List(Of Double())
            For i As Integer = 0 To 3
                Dim corner As Double() = SideIntersection(edges(order((i + 3) Mod 4)), edges(order(i)))
                If corner Is Nothing Then Exit For
                polygon.Add(corner)
            Next
            If polygon.Count <> 4 OrElse Not ValidInferredBoundary(edges, order, polygon, tol) Then Continue For
            If found Is Nothing Then
                found = polygon
            Else
                For Each corner As Double() In polygon
                    Dim matches As Boolean = False
                    For Each priorCorner As Double() In found
                        If Near(corner, priorCorner, tol) Then matches = True
                    Next
                    If Not matches Then Throw New InvalidOperationException("The four sides give an ambiguous outline. Select clearer outer boundary segments.")
                Next
            End If
        Next
    Next
    If found Is Nothing Then
        Throw New InvalidOperationException("The selected segments do not define a closed four-sided outline. " & _
            "Pick one straight segment from each outer side. Split or obscured sides are supported for convex shapes; " & _
            "a concave shape requires four edges whose endpoints meet.")
    End If
    Return found
End Function

Function SideIntersection(a As Double(), b As Double()) As Double()
    Dim ax As Double = a(2) - a(0), ay As Double = a(3) - a(1)
    Dim bx As Double = b(2) - b(0), by As Double = b(3) - b(1)
    Dim al As Double = Math.Sqrt(ax * ax + ay * ay), bl As Double = Math.Sqrt(bx * bx + by * by)
    ax /= al : ay /= al : bx /= bl : by /= bl
    Dim determinant As Double = ax * by - ay * bx
    ' Reject parallel or numerically unstable, almost parallel adjacent sides.
    If Math.Abs(determinant) <= 0.00000001 Then Return Nothing
    Dim t As Double = ((b(0) - a(0)) * by - (b(1) - a(1)) * bx) / determinant
    Dim x As Double = a(0) + t * ax, y As Double = a(1) + t * ay
    If Double.IsNaN(x) OrElse Double.IsInfinity(x) OrElse Double.IsNaN(y) OrElse Double.IsInfinity(y) Then Return Nothing
    Return New Double() {x, y}
End Function

Function ValidInferredBoundary(edges As List(Of Double()), order As Integer(), polygon As List(Of Double()), tol As Double) As Boolean
    Dim winding As Integer = 0
    For i As Integer = 0 To 3
        Dim a As Double() = polygon(i), b As Double() = polygon((i + 1) Mod 4)
        Dim c As Double() = polygon((i + 2) Mod 4)
        Dim dx As Double = b(0) - a(0), dy As Double = b(1) - a(1)
        Dim length As Double = Math.Sqrt(dx * dx + dy * dy)
        If Not IsFinitePositive(length) OrElse length <= tol Then Return False
        Dim turn As Double = Cross(a, b, c)
        If Math.Abs(turn) <= tol * length Then Return False
        If winding = 0 Then winding = Math.Sign(turn)
        If Math.Sign(turn) <> winding Then Return False ' Only convex inference is unambiguous.
        Dim edge As Double() = edges(order(i))
        For endpoint As Integer = 0 To 1
            Dim px As Double = edge(endpoint * 2) - a(0), py As Double = edge(endpoint * 2 + 1) - a(1)
            Dim distanceAlong As Double = px * dx / length + py * dy / length
            Dim distanceOff As Double = Math.Abs(px * dy / length - py * dx / length)
            ' Both selected endpoints must actually lie on this inferred side.
            ' Do not accept four arbitrary lines or segments beyond the corners.
            If distanceAlong < -tol OrElse distanceAlong > length + tol OrElse distanceOff > tol Then Return False
        Next
    Next
    Return True
End Function

Function OrderBoundary(edges As List(Of Double()), tol As Double) As List(Of Double())
    If edges.Count <> 4 Then Throw New InvalidOperationException("Select exactly four edges.")
    Dim vertices As New List(Of Double())
    Dim links As New List(Of Integer())
    For Each edge As Double() In edges
        Dim pair(1) As Integer
        For endpoint As Integer = 0 To 1
            Dim p As Double() = {edge(endpoint * 2), edge(endpoint * 2 + 1)}
            Dim found As Integer = -1
            For i As Integer = 0 To vertices.Count - 1
                If Near(p, vertices(i), tol) Then
                    If found >= 0 Then Throw New InvalidOperationException("Boundary corners are too close together.")
                    found = i
                End If
            Next
            If found < 0 Then
                vertices.Add(p)
                found = vertices.Count - 1
            End If
            pair(endpoint) = found
        Next
        If pair(0) = pair(1) Then Throw New InvalidOperationException("A selected edge has zero or negligible length.")
        For Each prior As Integer() In links
            If (pair(0) = prior(0) AndAlso pair(1) = prior(1)) OrElse _
               (pair(0) = prior(1) AndAlso pair(1) = prior(0)) Then
                Throw New InvalidOperationException("The same boundary edge was selected more than once.")
            End If
        Next
        links.Add(pair)
    Next
    If vertices.Count <> 4 Then Throw New InvalidOperationException("The edges must meet at four corners to form a closed boundary.")
    Dim degree(3) As Integer
    For Each link As Integer() In links
        degree(link(0)) += 1 : degree(link(1)) += 1
    Next
    For Each d As Integer In degree
        If d <> 2 Then Throw New InvalidOperationException("Each corner must join exactly two selected edges.")
    Next
    Dim polygon As New List(Of Double())
    Dim used(3) As Boolean
    Dim current As Integer = links(0)(0)
    For stepIndex As Integer = 0 To 3
        polygon.Add(vertices(current))
        Dim nextEdge As Integer = -1
        For i As Integer = 0 To 3
            If Not used(i) AndAlso (links(i)(0) = current OrElse links(i)(1) = current) Then
                nextEdge = i
                Exit For
            End If
        Next
        If nextEdge < 0 Then Throw New InvalidOperationException("The edges do not form one closed loop.")
        used(nextEdge) = True
        current = If(links(nextEdge)(0) = current, links(nextEdge)(1), links(nextEdge)(0))
    Next
    If current <> links(0)(0) Then Throw New InvalidOperationException("The boundary is not closed.")
    If SegmentsMeet(polygon(0), polygon(1), polygon(2), polygon(3), tol) OrElse _
       SegmentsMeet(polygon(1), polygon(2), polygon(3), polygon(0), tol) Then
        Throw New InvalidOperationException("The boundary crosses or touches itself.")
    End If
    For i As Integer = 0 To 3
        Dim a As Double() = polygon(i), b As Double() = polygon((i + 1) Mod 4)
        Dim c As Double() = polygon((i + 2) Mod 4)
        Dim length As Double = Math.Sqrt((b(0) - a(0)) ^ 2 + (b(1) - a(1)) ^ 2)
        If Math.Abs(Cross(a, b, c)) <= tol * length Then
            Throw New InvalidOperationException("The boundary must have four distinct, non-collinear corners.")
        End If
    Next
    Return polygon
End Function

Function SegmentsMeet(a As Double(), b As Double(), c As Double(), d As Double(), tol As Double) As Boolean
    If Math.Max(a(0), b(0)) < Math.Min(c(0), d(0)) - tol OrElse _
       Math.Max(c(0), d(0)) < Math.Min(a(0), b(0)) - tol OrElse _
       Math.Max(a(1), b(1)) < Math.Min(c(1), d(1)) - tol OrElse _
       Math.Max(c(1), d(1)) < Math.Min(a(1), b(1)) - tol Then Return False
    Dim abTol As Double = tol * Math.Sqrt((b(0) - a(0)) ^ 2 + (b(1) - a(1)) ^ 2)
    Dim cdTol As Double = tol * Math.Sqrt((d(0) - c(0)) ^ 2 + (d(1) - c(1)) ^ 2)
    Dim ac As Double = Cross(a, b, c), ad As Double = Cross(a, b, d)
    Dim ca As Double = Cross(c, d, a), cb As Double = Cross(c, d, b)
    Return Not ((ac > abTol AndAlso ad > abTol) OrElse (ac < -abTol AndAlso ad < -abTol) OrElse _
                (ca > cdTol AndAlso cb > cdTol) OrElse (ca < -cdTol AndAlso cb < -cdTol))
End Function

Function AreaCentroid(polygon As List(Of Double()), tol As Double) As Double()
    ' Translate to the first vertex to reduce cancellation at large sheet coordinates.
    Dim ox As Double = polygon(0)(0), oy As Double = polygon(0)(1)
    Dim twiceArea As Double = 0, sx As Double = 0, sy As Double = 0
    Dim perimeter As Double = 0
    For i As Integer = 0 To polygon.Count - 1
        Dim a As Double() = polygon(i), b As Double() = polygon((i + 1) Mod polygon.Count)
        Dim ax As Double = a(0) - ox, ay As Double = a(1) - oy
        Dim bx As Double = b(0) - ox, by As Double = b(1) - oy
        Dim term As Double = ax * by - bx * ay
        twiceArea += term : sx += (ax + bx) * term : sy += (ay + by) * term
        perimeter += Math.Sqrt((bx - ax) ^ 2 + (by - ay) ^ 2)
    Next
    If Math.Abs(twiceArea) <= tol * perimeter Then Throw New InvalidOperationException("The boundary has zero or negligible area.")
    Return New Double() {ox + sx / (3 * twiceArea), oy + sy / (3 * twiceArea)}
End Function

Function InteriorCount(span As Double, spacing As Double, tol As Double, limit As Integer) As Integer
    If Not IsFinitePositive(spacing) Then Throw New InvalidOperationException("Grid spacing is too small or invalid after view scaling.")
    If span <= tol Then Throw New InvalidOperationException("The boundary is too small.")
    Dim ratio As Double = (span - tol) / spacing
    If Double.IsInfinity(ratio) OrElse ratio > limit + 1 Then
        Throw New InvalidOperationException("Too many grid lines. Increase the spacing (maximum " & limit & " grid positions).")
    End If
    Return Math.Max(0, CInt(Math.Ceiling(ratio)) - 1)
End Function

Function ClipAxis(polygon As List(Of Double()), vertical As Boolean, position As Double, tol As Double) As List(Of Double())
    Dim axis As Integer = If(vertical, 0, 1), other As Integer = 1 - axis
    Dim hits As New List(Of Double)
    For i As Integer = 0 To polygon.Count - 1
        Dim a As Double() = polygon(i), b As Double() = polygon((i + 1) Mod polygon.Count)
        Dim delta As Double = b(axis) - a(axis)
        If Math.Abs(delta) <= tol Then
            If Math.Abs(position - a(axis)) <= tol Then
                hits.Add(a(other)) : hits.Add(b(other))
            End If
        Else
            Dim t As Double = (position - a(axis)) / delta
            If t >= 0 AndAlso t <= 1 Then hits.Add(a(other) + t * (b(other) - a(other)))
        End If
    Next
    hits.Sort()
    Dim unique As New List(Of Double)
    For Each hit As Double In hits
        If unique.Count = 0 OrElse Math.Abs(hit - unique(unique.Count - 1)) > tol Then unique.Add(hit)
    Next
    Dim result As New List(Of Double())
    For i As Integer = 0 To unique.Count - 2
        Dim lo As Double = unique(i), hi As Double = unique(i + 1)
        If hi - lo <= tol Then Continue For
        Dim middle As Double() = If(vertical, New Double() {position, (lo + hi) / 2}, New Double() {(lo + hi) / 2, position})
        If InsidePolygon(polygon, middle, tol) Then
            result.Add(If(vertical, New Double() {position, lo, position, hi}, New Double() {lo, position, hi, position}))
        End If
    Next
    Return result
End Function

Function InsidePolygon(polygon As List(Of Double()), p As Double(), tol As Double) As Boolean
    Dim inside As Boolean = False
    For i As Integer = 0 To polygon.Count - 1
        Dim a As Double() = polygon(i), b As Double() = polygon((i + 1) Mod polygon.Count)
        Dim length As Double = Math.Sqrt((b(0) - a(0)) ^ 2 + (b(1) - a(1)) ^ 2)
        ' Boundary is included so an axis through a concave corner remains well defined.
        If Math.Abs(Cross(a, b, p)) <= tol * length AndAlso _
           p(0) >= Math.Min(a(0), b(0)) - tol AndAlso p(0) <= Math.Max(a(0), b(0)) + tol AndAlso _
           p(1) >= Math.Min(a(1), b(1)) - tol AndAlso p(1) <= Math.Max(a(1), b(1)) + tol Then Return True
        If (a(1) > p(1)) <> (b(1) > p(1)) Then
            Dim crossing As Double = a(0) + (p(1) - a(1)) * (b(0) - a(0)) / (b(1) - a(1))
            If p(0) < crossing Then inside = Not inside
        End If
    Next
    Return inside
End Function
' GEOMETRY KERNEL END
